# Synthesize isogrid tubes


import FreeCAD
import math
import Draft
import Part
import collections

# mm
# cylinder dimensions
RADIUS = 50.0
THICKNESS = 1.0
LENGTH = 100.0

SKIRT_LENGTH = 2.0

# isogrid dimensions
SLICE_LENGTH = 10
SLICES = LENGTH / SLICE_LENGTH
# multiple of 2 per slice
SEGMENTS = 20
RIB_WIDTH = 1.0
RIB_DEPTH = 2.0
RIB_DIVISIONS = 5
#RIB_DIVISIONS = 1

# clipping plane angle in degrees
PLANE_ANGLE = -22.5

TOP_ASPECT = 1.0
PLANE_SLOPE = 0.0
PLANE_INTERCEPT = 0.0


# arrays of points of all tube segments
# points are in polar coordinates
slices = []
doc = App.activeDocument()


def toRad(angle):
    return angle * math.pi * 2.0 / 360.0

def polarToXYZ(angle, radius, z):
    x = radius * math.cos(angle)
    y = -radius * math.sin(angle)
    fraction = z / LENGTH
    aspect = (TOP_ASPECT * fraction) + (1.0 - fraction)
    x = x * aspect
    return Draft.Vector(x, y, z)

def polarToXYZ2(point):
    angle = point.x
    radius = point.y
    z = point.z
    return polarToXYZ(angle, radius, z)

def XYZToPolar(xyz):
    fraction = xyz.z / LENGTH
    aspect = (TOP_ASPECT * fraction) + (1.0 - fraction)
    xyz.x = xyz.x / aspect
    angle = math.atan2(-xyz.y, xyz.x)
    radius = math.hypot(xyz.x, xyz.y)
    return Draft.Vector(angle, radius, xyz.z)

def appendArray(dst, src):
    for i in src:
        dst.append(i)

# clip line in polar coordinates to the clipping plane
# returns True if the entire line is above the plane
newPoint1 = Draft.Vector(0.0, 0.0, 0.0)
newPoint2 = Draft.Vector(0.0, 0.0, 0.0)
def clipLine(point1, point2):
    global newPoint1
    global newPoint2
    newPoint1 = point1
    newPoint2 = point2
    xyz1 = polarToXYZ2(point1)
    xyz2 = polarToXYZ2(point2)

    planeZ1 = PLANE_INTERCEPT + xyz1.x * PLANE_SLOPE
    planeZ2 = PLANE_INTERCEPT + xyz2.x * PLANE_SLOPE

    if xyz1.z > planeZ1 and xyz2.z > planeZ2:
        return True

    if True:
        if xyz1.z > planeZ1:
            if abs(xyz2.x - xyz1.x) < 0.01:
                # vertical line
                print('clipLine 2')
                newPoint1.z = planeZ1
            else:
                # brute force intersection between line & plane
                #print('clipLine 3 point1 clipped')
                steps = 100
                for i in range(1, steps):
                    testPoint = xyz2 + (xyz1 - xyz2) * i / steps
                    testZ = PLANE_INTERCEPT + testPoint.x * PLANE_SLOPE
                    if testPoint.z >= testZ:
                        testPoint = xyz2 + (xyz1 - xyz2) * (i - 1) / steps
                        newPoint1 = XYZToPolar(testPoint)
                        break

        if xyz2.z > planeZ2:
            if abs(xyz2.x - xyz1.x) < 0.01:
                # vertical line
                #print('clipLine 4 point2.z=', newPoint2.z, ' planeZ2=', planeZ2)
                newPoint2.z = planeZ2
            else:
                # brute force intersection between line & plane
                testFraction = 0.5
                step = 0.5
                while step > 0.001:
                    testPoint = xyz1 + (xyz2 - xyz1) * testFraction
                    testZ = PLANE_INTERCEPT + testPoint.x * PLANE_SLOPE
                    step /= 2
                    if testPoint.z > testZ:
                        testFraction -= step
                    else:
                        testFraction += step
                testPoint = xyz1 + (xyz2 - xyz1) * testFraction
                newPoint2 = XYZToPolar(testPoint)


    return False

# requires coplanar points in each face
#def loftQuads(faces):
#    loft = doc.addObject('Part::Loft','Loft')
#    loft.Sections = faces
#    loft.Solid = True
#    loft.Ruled = False
#    loft.Closed = False
#    return loft

# split quads into triangles to handle non planar quads
def loftTris(topCoords, bottomCoords):
    faces = [
        Draft.makeWire([topCoords[0], topCoords[1], topCoords[2]], closed=True, face=False),
        Draft.makeWire([bottomCoords[0], bottomCoords[1], bottomCoords[2]], closed=True, face=False)
        ]

    loft = doc.addObject('Part::Loft','Loft')
    loft.Sections = faces
    loft.Solid = True
    loft.Ruled = False
    loft.Closed = False
    
    faces = [
        Draft.makeWire([topCoords[0], topCoords[2], topCoords[3]], closed=True, face=False),
        Draft.makeWire([bottomCoords[0], bottomCoords[2], bottomCoords[3]], closed=True, face=False)
        ]

    loft = doc.addObject('Part::Loft','Loft')
    loft.Sections = faces
    loft.Solid = True
    loft.Ruled = False
    loft.Closed = False




# join 2 points on a cylinder with a solid tube
# points are polar coords
def makeCylinderLine(start, end, divisions, ribWidth, ribDepth):
    depthVector = Draft.Vector(0, ribDepth)
    lofts = []
    for i in range(0, divisions):
        faces = []
        center1 = start + (end - start) * i / divisions
        center2 = start + (end - start) * (i + 1) / divisions
        if not clipLine(center1, center2):
            center1 = newPoint1
            center2 = newPoint2


            # get perpendicular vector on the surface of the cylinder
            diff = center2 - center1
            # get perpendicular vector in mm
            perpX = diff.z
            perpZ = math.sin(diff.x) * RADIUS
            perpMag = math.hypot(perpX, perpZ)
            perpX = perpX / perpMag * ribWidth / 2
            perpZ = perpZ / perpMag * ribWidth / 2
            # get perpendicular vector in polar coords
            perpVector = Draft.Vector(-math.asin(perpX / RADIUS), 0, perpZ)


            point0 = center1 - perpVector
            point1 = center1 - perpVector + depthVector
            point2 = center1 + perpVector + depthVector
            point3 = center1 + perpVector
            points1 = [ polarToXYZ(point0.x, point0.y, point0.z),
                polarToXYZ(point1.x, point1.y, point1.z),
                polarToXYZ(point2.x, point2.y, point2.z),
                polarToXYZ(point3.x, point3.y, point3.z) ]
            #faces.append(Draft.makeWire(points, closed=True, face=False))

            point0 = center2 - perpVector
            point1 = center2 - perpVector + depthVector
            point2 = center2 + perpVector + depthVector
            point3 = center2 + perpVector
            points2 = [polarToXYZ(point0.x, point0.y, point0.z),
                polarToXYZ(point1.x, point1.y, point1.z),
                polarToXYZ(point2.x, point2.y, point2.z),
                polarToXYZ(point3.x, point3.y, point3.z) ]
            #faces.append(Draft.makeWire(points, closed=True, face=False))

            loftTris(points1, points2)
            
            
            #loft = doc.addObject('Part::Loft','Loft')
            #loft.Sections = faces
            #loft.Solid = True
            #loft.Ruled = False
            #loft.Closed = False

            #lofts.append(loft)

#    App.activeDocument().recompute()
#    obj=Draft.clone(loft)
#    FreeCAD.ActiveDocument.removeObject(loft.Name)
#    for i in faces:
#        FreeCAD.ActiveDocument.removeObject(i.Name)

#    return obj      
    return lofts


def makeIsogrid():
    # create points defining the tube
    # divide tube into slices
    for slice in range(0, SLICES + 1):
        z = slice * LENGTH / SLICES
        segments = []
        # for each slice, we have a number of segments + 1 overlapping point
        for segment in range(0, SEGMENTS + 1):
            angle = toRad(segment * 360 / SEGMENTS)
            point = Draft.Vector(angle, RADIUS, z)
            segments.append(point)
        slices.append(segments)

    objects = []

# test line
#    makeCylinderLine(Draft.Vector(0.0, RADIUS, 0.0), 
#        Draft.Vector(45.0, RADIUS, 100.0), 
#        RIB_DIVISIONS, 
#        RIB_WIDTH, 
#        RIB_DEPTH)

    # create longerons
    if True:
        print('Longerons')
        for slice in range(0, SLICES):
#        for slice in range(0, 1):
            for segment in range(0, SEGMENTS):
                print('slice=', slice, ' segment=', segment)
                point0 = slices[slice][segment]
                point1 = slices[slice + 1][segment]
                obj = makeCylinderLine(point0, point1, 1, RIB_WIDTH, RIB_DEPTH)
                appendArray(objects, obj)

    # create diagonals
    if True:
        print('Diagonals')
        for slice in range(0, SLICES):
#        for slice in range(7, SLICES):
            slice1 = slice
            slice2 = slice + 1
            segment = 0
            while segment < SEGMENTS:
                print('slice=', slice, ' segment=', segment)
                segment1 = segment
                segment2 = segment + 1
                segment3 = segment + 2
                segment += 2

                if (slice % 2) == 0:
                    point0 = slices[slice1][segment1]
                    point1 = slices[slice2][segment2]
                    point2 = slices[slice1][segment3]
                    obj = makeCylinderLine(point0, point1, RIB_DIVISIONS, RIB_WIDTH, RIB_DEPTH)
                    appendArray(objects, obj)
                    obj = makeCylinderLine(point1, point2, RIB_DIVISIONS, RIB_WIDTH, RIB_DEPTH)
                    appendArray(objects, obj)
                else:
                    point0 = slices[slice2][segment1]
                    point1 = slices[slice1][segment2]
                    point2 = slices[slice2][segment3]
                    obj = makeCylinderLine(point0, point1, RIB_DIVISIONS, RIB_WIDTH, RIB_DEPTH)
                    appendArray(objects, obj)
                    obj = makeCylinderLine(point1, point2, RIB_DIVISIONS, RIB_WIDTH, RIB_DEPTH)
                    appendArray(objects, obj)

#    print('Fusing')
#    fusion = App.activeDocument().addObject("Part::MultiFuse","Fusion")
#    fusion.Shapes = objects
    return objects


#def clipPoint(point):
#    planeZ = PLANE_INTERCEPT + point.x * PLANE_SLOPE
#    if point.z > planeZ:
#        point.z = planeZ
#    return point



def makeTube():
    i = 0.0
    step = 5.0
    points = []
    while i < 360.0:
#    while i < 10.0:
        # cylinder coords
        topPoint1 = Draft.Vector(toRad(i), RADIUS, LENGTH)
        bottomPoint1 = Draft.Vector(toRad(i), RADIUS, 0)
        clipLine(bottomPoint1, topPoint1)
        bottomPoint1 = newPoint1
        topPoint1 = newPoint2

        topPoint2 = Draft.Vector(toRad(i + step), RADIUS, LENGTH)
        bottomPoint2 = Draft.Vector(toRad(i + step), RADIUS, 0)
        clipLine(bottomPoint2, topPoint2)
        bottomPoint2 = newPoint1
        topPoint2 = newPoint2

        topPoint3 = Draft.Vector(toRad(i + step), RADIUS + THICKNESS, LENGTH)
        bottomPoint3 = Draft.Vector(toRad(i + step), RADIUS + THICKNESS, 0)
        clipLine(bottomPoint3, topPoint3)
        bottomPoint3 = newPoint1
        topPoint3 = newPoint2

        topPoint4 = Draft.Vector(toRad(i), RADIUS + THICKNESS, LENGTH)
        bottomPoint4 = Draft.Vector(toRad(i), RADIUS + THICKNESS, 0)
        clipLine(bottomPoint4, topPoint4)
        bottomPoint4 = newPoint1
        topPoint4 = newPoint2

        faces = []
        topXYZ1 = polarToXYZ2(topPoint1)
        topXYZ2 = polarToXYZ2(topPoint2)
        topXYZ3 = polarToXYZ2(topPoint3)
        topXYZ4 = polarToXYZ2(topPoint4)
        bottomXYZ1 = polarToXYZ2(bottomPoint1)
        bottomXYZ2 = polarToXYZ2(bottomPoint2)
        bottomXYZ3 = polarToXYZ2(bottomPoint3)
        bottomXYZ4 = polarToXYZ2(bottomPoint4)

        loftTris([topXYZ1, topXYZ2, topXYZ3, topXYZ4], 
            [bottomXYZ1, bottomXYZ2, bottomXYZ3, bottomXYZ4])


        
        # skirt points
        skirtOffset = Draft.Vector(0.0, 0.0, SKIRT_LENGTH / 2)

        topPoint3 = Draft.Vector(toRad(i + step), RADIUS + RIB_DEPTH, LENGTH)
        bottomPoint3 = Draft.Vector(toRad(i + step), RADIUS + RIB_DEPTH, 0)
        clipLine(bottomPoint3, topPoint3)
        bottomPoint3 = newPoint1
        topPoint3 = newPoint2

        topPoint4 = Draft.Vector(toRad(i), RADIUS + RIB_DEPTH, LENGTH)
        bottomPoint4 = Draft.Vector(toRad(i), RADIUS + RIB_DEPTH, 0)
        clipLine(bottomPoint4, topPoint4)
        bottomPoint4 = newPoint1
        topPoint4 = newPoint2

        topXYZ3 = polarToXYZ2(topPoint3)
        topXYZ4 = polarToXYZ2(topPoint4)
        bottomXYZ3 = polarToXYZ2(bottomPoint3)
        bottomXYZ4 = polarToXYZ2(bottomPoint4)

        # skirt objects
        # top skirt
        loftTris([topXYZ1 + skirtOffset, 
                topXYZ2 + skirtOffset, 
                topXYZ3 + skirtOffset, 
                topXYZ4 + skirtOffset],
            [topXYZ1 - skirtOffset, 
                topXYZ2 - skirtOffset, 
                topXYZ3 - skirtOffset, 
                topXYZ4 - skirtOffset])

        loftTris([bottomXYZ1 - skirtOffset, 
                bottomXYZ2 - skirtOffset, 
                bottomXYZ3 - skirtOffset, 
                bottomXYZ4 - skirtOffset], 
            [bottomXYZ1 + skirtOffset, 
                bottomXYZ2 + skirtOffset, 
                bottomXYZ3 + skirtOffset, 
                bottomXYZ4 + skirtOffset])


        i += step
    


# cutting object
def makeCube():
    cube = App.ActiveDocument.addObject("Part::Box","Box")
    cube.Length = '200 mm'
    cube.Width = '200 mm'
    cube.Height = '100 mm'
    cube.Placement = App.Placement(
        App.Vector(-cube.Length / 2, -cube.Width / 2, LENGTH),
        App.Rotation(App.Vector(0, 1, 0), 22.5))
    return cube

def trim(object, cutter):
    dst = App.activeDocument().addObject("Part::Cut","Cut")
    dst.Base = object
    dst.Tool = cutter
    return dst


# disable recomputes
App.ActiveDocument.RecomputesFrozen = True


# compute derived dimensions
# slope of the clipping plane Z/X
PLANE_SLOPE = math.tan(toRad(PLANE_ANGLE))
# where clipping plane intersects Z axis
PLANE_INTERCEPT = LENGTH + PLANE_SLOPE * (RADIUS + RIB_DEPTH)

x2 = math.cos(toRad(PLANE_ANGLE)) * RADIUS
z2 = PLANE_INTERCEPT + math.sin(toRad(PLANE_ANGLE)) * RADIUS
z3 = PLANE_INTERCEPT - math.sin(toRad(PLANE_ANGLE)) * RADIUS
slope3 = (x2 - RADIUS) / z2
slope4 = (x2 - RADIUS) / z3
x3 = RADIUS + slope3 * LENGTH
x4 = RADIUS + slope4 * LENGTH
print('x3=', x3, ' x4=', x4)


# amount to compress X at top of cylinder to get a round hole
TOP_ASPECT = (x3 + x4) / (RADIUS * 2)
print('TOP_ASPECT=', TOP_ASPECT)

makeIsogrid()
makeTube()

#App.activeDocument().recompute()









#cube = makeCube()
#print ('Boolean tube')
#cube = makeCube()
#trim(tube, cube)

#for i in isogrid:
#    print ('Boolean object=', i.Name)
#    cube = makeCube()
#    trim(i, cube)



#print('Fusing')
#fusion = App.activeDocument().addObject("Part::MultiFuse","Fusion")
#fusion.Shapes = objects

#cut = App.activeDocument().addObject("Part::Cut","Cut")
#cut.Base = fusion
#cut.Tool = cube
#Gui.activeDocument().hide(fusion.Name)
#Gui.activeDocument().hide(cube.Name)



#for i in isogrid:
#    print ('isogrid=', i.Name)
#    cube2 = Draft.clone(cube)
#    App.activeDocument().addObject("Part::Cut","Cut")
#    App.activeDocument().Cut.Base = i
#    App.activeDocument().Cut.Tool = cube2
#    Gui.activeDocument().hide(i.Name)
#    Gui.activeDocument().hide(cube2.Name)
