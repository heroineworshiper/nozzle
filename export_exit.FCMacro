# -*- coding: utf-8 -*-

# Macro Begin: /amazon2/root/nozzle/export_exit.FCMacro +++++++++++++++++++++++++++++++++++++++++++++++++
import FreeCAD
import Mesh

__objs__=[]
__objs__.append(FreeCAD.getDocument("final").getObject("Cut082"))
__objs__.append(FreeCAD.getDocument("final").getObject("exit"))
Mesh.export(__objs__,u"/amazon2/root/nozzle/exit.stl")

del __objs__
# Macro End: /amazon2/root/nozzle/export_exit.FCMacro +++++++++++++++++++++++++++++++++++++++++++++++++
