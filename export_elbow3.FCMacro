# -*- coding: utf-8 -*-

# Macro Begin: /amazon2/root/nozzle/export_elbow3.FCMacro +++++++++++++++++++++++++++++++++++++++++++++++++
import FreeCAD
import Mesh

__objs__=[]
__objs__.append(FreeCAD.getDocument("final").getObject("Part064"))
__objs__.append(FreeCAD.getDocument("final").getObject("Part__Mirroring"))
Mesh.export(__objs__,u"/amazon2/root/nozzle/elbow3.stl")

del __objs__
# Macro End: /amazon2/root/nozzle/export_elbow3.FCMacro +++++++++++++++++++++++++++++++++++++++++++++++++
