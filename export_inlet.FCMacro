# -*- coding: utf-8 -*-

# Macro Begin: /amazon2/root/nozzle/export_inlet.FCMacro +++++++++++++++++++++++++++++++++++++++++++++++++
import FreeCAD
import Mesh

__objs__=[]
__objs__.append(FreeCAD.getDocument("final").getObject("Part079"))
__objs__.append(FreeCAD.getDocument("final").getObject("Cut047"))
Mesh.export(__objs__,u"/amazon2/root/nozzle/inlet.stl")

del __objs__
# Macro End: /amazon2/root/nozzle/export_inlet.FCMacro +++++++++++++++++++++++++++++++++++++++++++++++++
